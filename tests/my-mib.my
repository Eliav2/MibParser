my-mib DEFINITIONS ::= BEGIN


frxT1OutOctets OBJECT-TYPE
    SYNTAX Counter
    ACCESS read-only
    STATUS mandatory
    DESCRIPTION
        "Number of octets transmitted to the network
        from this subscriber port"
    ::= { frxPortEntry 10 }

Counter ::=
           [APPLICATION 1]
               IMPLICIT INTEGER (0..4294967295)

frxPortEntry OBJECT-TYPE
    SYNTAX FrxPortEntry
    ACCESS not-accessible
    STATUS mandatory
    DESCRIPTION
        "A specific entry in the Cisco 90 Series Port Table. There is
        one entry for each port on each Cisco 90 Series channel unit
        in the system.  There are no entries for unused banks or
        empty channel unit slots."
    INDEX { frxBankIndex, frxChUIndex, frxPortIndex }
    ::= { frxPortTable 1 }

FrxPortEntry ::= SEQUENCE {
    frxPortSpeed INTEGER,
    frxPortProtocol INTEGER,
    frxDSLStatus INTEGER,
    frxPVCAssigned INTEGER,
    frxLastChange TimeTicks,
    frxBrite INTEGER,
    frxDSLInOctets Counter,
    frxDSLOutOctets Counter,
    frxT1InOctets Counter,
    frxT1OutOctets Counter,
    frxDSLBadFrames Counter,
    frxDSLHDLCEs Counter,
    frxDSLCRCEs Counter,
    frxDSLLinkEs Counter,
    frxDSLFrShEs Counter,
    frxDSLFrLgEs Counter,
    frxDSLDLCIEs Counter,
    frxTxBuf INTEGER,
    frxRxBuf INTEGER,
    frxPortNetEs Counter
    }

frxPortSpeed OBJECT-TYPE
    SYNTAX INTEGER {
        use56kbps(1),
        use64kbps(2),
        use128kbps(3),
        use144kbps(4)
        }
    ACCESS read-write
    STATUS mandatory
    DESCRIPTION
        "This is the speed that the channel unit port runs at.
          1=56kbps   2=64kbps   3=128kbps   4=144kbps
        This parameter can only be changed if frxConfigSrc is
        set to SNMP."
    ::= { frxPortEntry 1 }

frxPortProtocol OBJECT-TYPE
    SYNTAX INTEGER {
        frameRelay(1),
        ppp(2)
        }
    ACCESS read-write
    STATUS mandatory
    DESCRIPTION
        "This parameter controls what protocol the channel
        unit should expect the subscriber to send on the port.
          1=Port uses Frame Relay protocol - no encapsulation
          2=Port uses PPP protocol - do RFC-1973 encapsulation
        This parameter can only be changed if frxConfigSrc is
        set to SNMP."
    ::= { frxPortEntry 2 }

frxDSLStatus OBJECT-TYPE
    SYNTAX INTEGER {
        loopDown(1),
        dslSyncOnly(2),
        loopUpInactive(3),
        loopUp(4)
        }
    ACCESS read-only
    STATUS mandatory
    DESCRIPTION
        "This is the status of the DSL loop to the subscriber.
        1=Loop is down.
        2=Frx card has achieved physical layer activation with
          the first BRITE card or the NT1 if there are no BRITE cards.
        3=Link is up but Annex-D is still inactive.  The ACT bit has
          been exchanged with the NT1 indicating a clear channel path
          to the customer has been established. Ports running protocols
          (i.e. PPP) that do not support Annex-D will never be in this
          state.
        4=Link is fully up.  Annex-D (if appropriate) is active."
    ::= { frxPortEntry 3 }

frxPVCAssigned OBJECT-TYPE
    SYNTAX INTEGER(0..8)
    ACCESS read-only
    STATUS mandatory
    DESCRIPTION
        "Number of PVCs assigned to Subscriber Port as determined
        by Annex-D"
    ::= { frxPortEntry 4 }

frxLastChange OBJECT-TYPE
    SYNTAX TimeTicks
    ACCESS read-only
    STATUS mandatory
    DESCRIPTION
        "Time since DSL went in sync or lost sync in 0.01
        second increments."
    ::= { frxPortEntry 5 }

TimeTicks ::=
           [APPLICATION 3]
               IMPLICIT INTEGER (0..4294967295)

frxBrite OBJECT-TYPE
    SYNTAX INTEGER(0..6)
    ACCESS read-only
    STATUS mandatory
    DESCRIPTION
        "Number of BRITE cards downstream.  BRITE cards are used
        to extend the loop over subscriber loop carrier systems
        and are detected via a background polling operation."
    ::= { frxPortEntry 6 }

frxDSLInOctets OBJECT-TYPE
    SYNTAX Counter
    ACCESS read-only
    STATUS mandatory
    DESCRIPTION
        "Number of octets received from the subscriber DSL
        Does not include Annex-D octets"
    ::= { frxPortEntry 7 }

frxDSLOutOctets OBJECT-TYPE
    SYNTAX Counter
    ACCESS read-only
    STATUS mandatory
    DESCRIPTION
        "Number of octets transmitted to the subscriber DSL.
        Does not include Annex-D octets"
    ::= { frxPortEntry 8 }

frxT1InOctets OBJECT-TYPE
    SYNTAX Counter
    ACCESS read-only
    STATUS mandatory
    DESCRIPTION
        "Number of octets received from the network
        directed at this subscriber port"
    ::= { frxPortEntry 9 }

frxDSLBadFrames OBJECT-TYPE
    SYNTAX Counter
    ACCESS read-only
    STATUS mandatory
    DESCRIPTION
        "Total number of frames received from this subscriber port
        that were discarded. Possible reasons for discard are:
           Frame contained HDLC abort (7 or more ones in a row)
           Frame had a CRC error
           Frame had a non-integral number of bytes
           Frame was too short (less than 5 bytes)
           Frame was too long (more than 8192 bytes)
           Frame had illegal DLCI (not 16-23)
           Frame was discarded due to lack of buffer space or
              due to congestion control"
    ::= { frxPortEntry 11 }

frxDSLHDLCEs OBJECT-TYPE
    SYNTAX Counter
    ACCESS read-only
    STATUS mandatory
    DESCRIPTION
        "Subscriber port Errored Seconds caused by HDLC aborts
        (7 or more ones in a row). Total number of seconds in
        which a frame with an HDLC abort is received from this
        port."
    ::= { frxPortEntry 12 }

frxDSLCRCEs OBJECT-TYPE
    SYNTAX Counter
    ACCESS read-only
    STATUS mandatory
    DESCRIPTION
        "Subscriber port Errored Seconds caused by CRC errors.
        Total number of seconds in which a frame with a CRC
        error is received from this port."
    ::= { frxPortEntry 13 }

frxDSLLinkEs OBJECT-TYPE
    SYNTAX Counter
    ACCESS read-only
    STATUS mandatory
    DESCRIPTION
        "Subscriber port Errored Seconds caused by Non-integral
        Bytes. Total number of seconds in which a frame with a
        non-integral  number of bytes is received from this
        port."
    ::= { frxPortEntry 14 }

frxDSLFrShEs OBJECT-TYPE
    SYNTAX Counter
    ACCESS read-only
    STATUS mandatory
    DESCRIPTION
        "Subscriber port Errored Seconds caused by Short Frames.
        received Total number of seconds in which a frame that
        is too short (less than 5 bytes) is received from this
        port."
    ::= { frxPortEntry 15 }

frxDSLFrLgEs OBJECT-TYPE
    SYNTAX Counter
    ACCESS read-only
    STATUS mandatory
    DESCRIPTION
        "Subscriber port Errored Seconds caused by Long Frames
        received. Total number of seconds in which a frame that
        is too long (more than 8192 bytes) is received from this
        port."
    ::= { frxPortEntry 16 }

frxDSLDLCIEs OBJECT-TYPE
    SYNTAX Counter
    ACCESS read-only
    STATUS mandatory
    DESCRIPTION
        "Subscriber port Errored Seconds caused by illegal DLCI.
        Total number of seconds in which a frame that has a DLCI
        other than 16 to 23 (or 0) is received from this port."
    ::= { frxPortEntry 17 }

frxTxBuf OBJECT-TYPE
    SYNTAX INTEGER(0..65535)
    ACCESS read-only
    STATUS mandatory
    DESCRIPTION
        "Number of octets in the transmit buffer for this
        subscriber port.  This data is waiting to be sent
        to the network (T1)."
    ::= { frxPortEntry 18 }

frxRxBuf OBJECT-TYPE
    SYNTAX INTEGER(0..65535)
    ACCESS read-only
    STATUS mandatory
    DESCRIPTION
        "Number of octets in the receive buffer for this
        subscriber port.  This data is from the network (T1)
        and is waiting to be sent to the subscriber port."
    ::= { frxPortEntry 19 }

frxPortNetEs OBJECT-TYPE
    SYNTAX Counter
    ACCESS read-only
    STATUS mandatory
    DESCRIPTION
        "Total number of seconds in which a frame received
        from the network (T1) and targeted at this subscriber
        port was discarded."
    ::= { frxPortEntry 20 }

frxBankIndex OBJECT-TYPE
    SYNTAX INTEGER(16..1007)
    ACCESS read-only
    STATUS mandatory
    DESCRIPTION
        "Channel Bank Di-group Number. This index is used to address
        the various channel banks in the system. This number is the
        same as the DLCI number used to communicate with the bank at
        the Cisco 90 SNMP Agent. (note that this is NOT the same
        as the DLCI number at the channel bank.  The channel bank
        always uses DLCI 30 or 31 to communicate with the Agent.)"
    ::= { frxBankEntry 1 }

frxBankEntry OBJECT-TYPE
    SYNTAX FrxBankEntry
    ACCESS not-accessible
    STATUS mandatory
    DESCRIPTION
        "A specific entry in the Cisco 90 Series Bank Di-group
        Table. There is one entry for each channel bank di-group
        (T1) in the system. There are no entries for unused banks"
    INDEX { frxBankIndex }
    ::= { frxBankTable 1 }

FrxBankEntry ::= SEQUENCE {
    frxBankIndex INTEGER,
    frxBankType INTEGER
    }

frxBankType OBJECT-TYPE
    SYNTAX INTEGER {
        d4(1)
        }
    ACCESS read-write
    STATUS mandatory
    DESCRIPTION
        "This is the type of channel bank and is for future use.
        D4 banks return a value of 1."
    ::= { frxBankEntry 2 }

frxBankTable OBJECT-TYPE
    SYNTAX SEQUENCE OF FrxBankEntry
    ACCESS not-accessible
    STATUS mandatory
    DESCRIPTION
        "This Cisco 90 Series Bank Di-group Table contains channel
        bank level information for each of the channel bank di-groups
        in the system. A di-group is a T1 interface to the frame
        relay network. The table is indexed using the Cisco 90 Series
        channel bank digroup number"
    ::= { frxBank 1 }

frxBank         OBJECT IDENTIFIER ::= { frMux 3 }

frMux           OBJECT IDENTIFIER ::= { ciscoTelesend 1 }

ciscoTelesend   OBJECT IDENTIFIER ::= { enterprises 1570 }

enterprises   OBJECT IDENTIFIER ::= { private 1 }

private       OBJECT IDENTIFIER ::= { internet 4 }

internet      OBJECT IDENTIFIER ::= { iso org(3) dod(6) 1 }

frxChUIndex OBJECT-TYPE
    SYNTAX INTEGER(1..24)
    ACCESS read-only
    STATUS mandatory
    DESCRIPTION
        "Channel Unit Number.  This index is used to address a
        specific channel unit in a bank. For D4 channel banks
        this number is the same as the physical slot number 1-24"
    ::= { frxChUEntry 1 }

frxChUEntry OBJECT-TYPE
    SYNTAX FrxChUEntry
    ACCESS not-accessible
    STATUS mandatory
    DESCRIPTION
        "A specific entry in the Cisco 90 Series Channel Unit Table.
        There is one entry for each Cisco 90 Series channel unit in
        the system. There are no entries for unused banks or empty
        channel unit slots"
    INDEX { frxBankIndex, frxChUIndex }
    ::= { frxChUTable 1 }

FrxChUEntry ::= SEQUENCE {
    frxChUIndex INTEGER,
    frxChUType INTEGER,
    frxChUVersion INTEGER,
    frxSigProtocol INTEGER,
    frxConfigSrc INTEGER,
    frxDLCIAdLen INTEGER,
    frxNetInOctets Counter,
    frxNetOutOctets Counter,
    frxNetBadFrames Counter,
    frxNetHDLCEs Counter,
    frxNetCRCEs Counter,
    frxNetLinkEs Counter,
    frxNetFrShEs Counter,
    frxNetFrLgEs Counter,
    frxNetPPPEs Counter,
    frxNetBufEs Counter
    }

frxChUType OBJECT-TYPE
    SYNTAX INTEGER {
        cisco90i(100)
        }
    ACCESS read-only
    STATUS mandatory
    DESCRIPTION
        "Type of Cisco 90 Series channel unit installed."
    ::= { frxChUEntry 2 }

frxChUVersion OBJECT-TYPE
    SYNTAX INTEGER(0..65535)
    ACCESS read-only
    STATUS mandatory
    DESCRIPTION
        "Cisco 90 Series channel unit version number."
    ::= { frxChUEntry 3 }

frxSigProtocol OBJECT-TYPE
    SYNTAX INTEGER {
        annexD(1)
        }
    ACCESS read-only
    STATUS mandatory
    DESCRIPTION
        "This is the type of Local In-channel Signaling used
        when the subscriber is running frame relay protocol.
        It is provided for future use. Set to 1 for T1.617
        Annex-D"
    ::= { frxChUEntry 4 }

frxConfigSrc OBJECT-TYPE
    SYNTAX INTEGER {
        annexD(1),
        snmp(2)
        }
    ACCESS read-write
    STATUS mandatory
    DESCRIPTION
        "Source for configuring speed and protocol for each port.
         1=Data rate and protocol set by DLCI assignment rules
           as reported by Annex-D.  This option allows control
           of these basic parameters from the frame relay switch
           management station instead of the Cisco 90 Series
           management station.
         2=Data rate and protocol set by SNMP variables
           frxPortSpeed and frxPortProtocol"
    ::= { frxChUEntry 5 }

frxDLCIAdLen OBJECT-TYPE
    SYNTAX INTEGER {
        twoOctetDlci(1)
        }
    ACCESS read-only
    STATUS mandatory
    DESCRIPTION
        "The number of bytes used for the DLCI address.
        For future use.  1=two octets."
    ::= { frxChUEntry 6 }

frxNetInOctets OBJECT-TYPE
    SYNTAX Counter
    ACCESS read-only
    STATUS mandatory
    DESCRIPTION
        "Total number of octets received by this channel
        unit from Frame Relay Switch (on the T1 interface)
        Only frames whose DLCI is addressed to a port on
        this channel unit are counted.  Bad frames, Annex-D
        and SNMP frames are not counted. CRC bytes are not
        counted"
    ::= { frxChUEntry 7 }

frxNetOutOctets OBJECT-TYPE
    SYNTAX Counter
    ACCESS read-only
    STATUS mandatory
    DESCRIPTION
        "Total number of octets transmitted to the Frame
        Relay Switch (on the T1 interface) by this channel
        unit. Annex-D and SNMP frames are not counted. CRC
        bytes are not counted"
    ::= { frxChUEntry 8 }

frxNetBadFrames OBJECT-TYPE
    SYNTAX Counter
    ACCESS read-only
    STATUS mandatory
    DESCRIPTION
        "Total number of frames received on the network (T1)
        interface that are discarded by this channel unit.
        Possible reasons for discard are:
           Frame contained HDLC abort (7 or more ones in a row)
           Frame had a CRC error
           Frame had a non-integral number of bytes
           Frame was too short (less than 5 bytes)
           Frame was too long (more than 8192 bytes)
           Frame had bad RFC-1973 (PPP) header - this error only
              occurs if destination port is set for PPP protocol.
           Frame was discarded due to lack of buffer space.
        Only frames whose DLCI is addressed to a port on
        this channel unit are counted."
    ::= { frxChUEntry 9 }

frxNetHDLCEs OBJECT-TYPE
    SYNTAX Counter
    ACCESS read-only
    STATUS mandatory
    DESCRIPTION
        "Network Errored Seconds caused by HDLC aborts (7 or more
        ones in a row). Total number of seconds in which a frame
        with an HDLC abort is received by this channel unit on
        the network (T1) interface. Only frames whose DLCI is
        addressed to a port on this channel unit are counted."
    ::= { frxChUEntry 10 }

frxNetCRCEs OBJECT-TYPE
    SYNTAX Counter
    ACCESS read-only
    STATUS mandatory
    DESCRIPTION
        "Network Errored Seconds caused by CRC errors.
        Total number of seconds in which a frame with a CRC
        error is received by this channel unit on the network
        (T1) interface. Only frames whose DLCI is addressed
        to a port on this channel unit are counted."
    ::= { frxChUEntry 11 }

frxNetLinkEs OBJECT-TYPE
    SYNTAX Counter
    ACCESS read-only
    STATUS mandatory
    DESCRIPTION
        "Network Errored Seconds caused by Non-integral Bytes.
        Total number of seconds in which a frame with a non-integral
        number of bytes is received by this channel unit on the
        network (T1) interface. Only frames whose DLCI is addressed
        to a port on this channel unit are counted."
    ::= { frxChUEntry 12 }

frxNetFrShEs OBJECT-TYPE
    SYNTAX Counter
    ACCESS read-only
    STATUS mandatory
    DESCRIPTION
        "Network Errored Seconds caused by Short Frames received.
        Total number of seconds in which a frame that is too
        short (less than 5 bytes) is received by this channel
        unit on the network (T1) interface. Only frames whose
        DLCI is addressed to a port on this channel unit are
        counted."
    ::= { frxChUEntry 13 }

frxNetFrLgEs OBJECT-TYPE
    SYNTAX Counter
    ACCESS read-only
    STATUS mandatory
    DESCRIPTION
        "Network Errored Seconds caused by Long Frames received.
        Total number of seconds in which a frame that is too
        long (more than 8192 bytes) is received by this channel
        unit on the network (T1) interface. Only frames whose
        DLCI is addressed to a port on this channel unit are
        counted."
    ::= { frxChUEntry 14 }

frxNetPPPEs OBJECT-TYPE
    SYNTAX Counter
    ACCESS read-only
    STATUS mandatory
    DESCRIPTION
        "Errored seconds caused by bad RFC-1973 (PPP) header.
        Total number of seconds in which a frame with an
        invalid RFC-1973 (PPP) header is received by this
        channel unit on the network (T1) interface. Only frames
        whose DLCI is addressed to a port that is set to PPP
        protocol and is on this channel unit are counted."
    ::= { frxChUEntry 15 }

frxNetBufEs OBJECT-TYPE
    SYNTAX Counter
    ACCESS read-only
    STATUS mandatory
    DESCRIPTION
        "Errored Seconds caused by Buffer Overflow.
        Total number of seconds in which a frame received
        by this channel unit on the network (T1) interface
        was discarded due to insufficient buffer space. Only
        frames whose DLCI is addressed to a port on this
        channel unit are counted."
    ::= { frxChUEntry 16 }

frxChUTable OBJECT-TYPE
    SYNTAX SEQUENCE OF FrxChUEntry
    ACCESS not-accessible
    STATUS mandatory
    DESCRIPTION
        "This Cisco 90 Series Channel Unit Table contains channel unit
        level control and statistics for each of the Cisco 90 Series
        channel units in the system. The table is indexed
        first using the Cisco 90 Series channel bank digroup number,
        then the channel unit number (1 to 24)."
    ::= { frxChUnit 1 }

frxChUnit       OBJECT IDENTIFIER ::= { frMux 4 }

frxPortIndex OBJECT-TYPE
    SYNTAX INTEGER(0..3)
    ACCESS read-only
    STATUS mandatory
    DESCRIPTION
        "Which subscriber port on the channel unit is
        addressed.  Ports are numbered from 0 to 3.
        Some channel unit types have less than 4 ports."
    ::= { frxMgtPortEntry 1 }

frxMgtPortEntry OBJECT-TYPE
    SYNTAX FrxMgtPortEntry
    ACCESS not-accessible
    STATUS mandatory
    DESCRIPTION
        "A specific entry in the Cisco 90 Series Management Port
        Table. There is one entry for each port on each
        Cisco 90 Series channel unit in the system.  There are no
        entries  for unused banks or empty channel unit
        slots."
    INDEX { frxBankIndex, frxChUIndex, frxPortIndex }
    ::= { frxMgtPortTable 1 }

FrxMgtPortEntry ::= SEQUENCE {
    frxPortIndex INTEGER,
    frxPortLinkErrors Counter,
    frxPortProtErrors Counter,
    frxPortChInactive Counter
    }

frxPortLinkErrors OBJECT-TYPE
    SYNTAX Counter
    ACCESS read-only
    STATUS mandatory
    DESCRIPTION
        "Number of signaling link reliability errors from
        subscriber port.  A signaling reliability error is
        declared whenever the channel units did not receive
        an Annex-D link integrity poll or full status inquiry
        poll from the subscriber port within the required time."
    ::= { frxMgtPortEntry 2 }

frxPortProtErrors OBJECT-TYPE
    SYNTAX Counter
    ACCESS read-only
    STATUS mandatory
    DESCRIPTION
        "Number of signaling protocol errors from subscriber
        port. A signaling protocol error is declared whenever
        the channel units receive an Annex-D link integrity
        poll or full status inquiry poll with incorrect
        format or sequence numbers from the subscriber port."
    ::= { frxMgtPortEntry 3 }

frxPortChInactive OBJECT-TYPE
    SYNTAX Counter
    ACCESS read-only
    STATUS mandatory
    DESCRIPTION
        "Number of times the subscriber port Annex-D signaling
        channel was declared inactive"
    ::= { frxMgtPortEntry 4 }

frxMgtPortTable OBJECT-TYPE
    SYNTAX SEQUENCE OF FrxMgtPortEntry
    ACCESS not-accessible
    STATUS mandatory
    DESCRIPTION
        "This table monitors the T1-617 Annex-D link
        between the channel units and the subscribers.
        There is one table row for every port on every
        channel unit in every bank. The table is indexed
        first using the channel bank digroup number, then
        the channel unit number (1 to 24), and then the
        port number (0 to 3)."
    ::= { frxMgt 2 }

frxMgt          OBJECT IDENTIFIER ::= { frMux 5 }

frxPortTable OBJECT-TYPE
    SYNTAX SEQUENCE OF FrxPortEntry
    ACCESS not-accessible
    STATUS mandatory
    DESCRIPTION
        "This Cisco 90 Series Port Table contains per-port control and
        statistics for each of the subscriber ports in the
        system. The table is indexed first using the Cisco 90 Series
        channel bank digroup number, then by the channel
        unit number (1 to 24), and finally by the port
        number (0-3)."
    ::= { frxPort 1 }

frxPort         OBJECT IDENTIFIER ::= { frMux 6 }




END
